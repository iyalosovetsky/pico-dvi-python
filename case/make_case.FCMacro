# Parametric enclosure for Waveshare PICO-DVI-LCD 7" + Raspberry Pi Pico 2 W.
#
# Run in FreeCAD (Macro > Macros... > make_case.FCMacro) or headless:
#   freecadcmd -c "exec(open('case/make_case.FCMacro').read())"
# Builds/updates case/case.FCStd with a "Params" spreadsheet; edit values there
# (or the defaults below) and run the macro again. Also exports STL + STEP.
#
# Parts (print without supports):
#   Bezel - front plate, printed face down. Holds the panel in a pocket and
#           drops into the front rebate of the back (its walls run up to the
#           front face), so the side walls are one piece and the seam is hidden.
#   Back  - thin rear cover: its back plate lies on the driver board standoffs.
#           Wall-mount keyholes, a window for the heatsink, an opening over the
#           Pico; printed back down. 4x M3 screws go through bosses in the back
#           into the bezel (self-tapping M3, or heat-set inserts with
#           screw_pilot = 4.0), 2x M3 into the lower board standoffs.
#   Cap   - separate hump over the Pico; its lip goes into the opening and
#           4 snap fingers (long sides) click under the plate edge; printed
#           roof down. The USB-C plug lies under the back plate, the
#           cable leaves through a hole in it into the gap behind the case.
#   Feet  - two spacers at the bottom of the back, as high as the cap, so the
#           case hangs straight on the wall. Each is held by an M3 x 8 screwed
#           from inside the back (before the bezel goes on) into its pilot hole.
import math
import os

import FreeCAD as App
import Part
from FreeCAD import Vector as V

HERE = os.path.dirname(os.path.abspath(__file__)) if "__file__" in dir() else os.path.join(os.getcwd(), "case")

# name: (default, comment). All sizes in mm, X = width, Y = height (up),
# Z = depth: Z = 0 is the front face, Z grows towards the back. +X points to
# the RIGHT when looking at the BACK (left when looking at the screen).
DEFAULTS = [
    ("panel_w", 164.7, "LCD module outline width (Waveshare: 164.70)"),
    ("panel_h", 100.0, "LCD module outline height (Waveshare: 100.00)"),
    ("panel_t", 3.6, "LCD module thickness (measured)"),
    ("border_top", 5.6, "panel edge to visible area, top (measured, seen from the front)"),
    ("border_bottom", 9.2, "panel edge to visible area, bottom (FPC side)"),
    ("border_left", 2.9, "panel edge to visible area, left"),
    ("border_right", 5.6, "panel edge to visible area, right"),
    ("frame_sym", 1, "1 = window exactly over the visible area, case widened on the narrow"
                     " border side so the visible frame is symmetric"),
    ("window_margin", 0.3, "window larger than the visible area on each side"),
    ("fit", 0.4, "clearance around the panel"),
    ("fpc_x", 0.5, "panel FPC (flat cable) centre X on the bottom edge (seen from the back), from photo"),
    ("fpc_w", 36.0, "FPC relief width (FPC ~28 mm + margin)"),
    ("fpc_out", 4.5, "FPC relief past the panel edge (FPC bend sticks out 3-4 mm)"),
    ("fpc_relief", 1.2, "FPC relief in the back cover clamp where the FPC lies on the panel back"),
    ("border", 8.0, "frame width outside the panel pocket (room for screw bosses)"),
    ("front_t", 2.0, "front plate thickness"),
    ("wall", 1.5, "side wall / back plate thickness"),
    ("lid_fit", 0.2, "gap between the bezel and the back walls around it"),
    ("press_skirt", 4.5, "panel clamp: flat ring width (3 mm on the panel border), then a"
                         " hollow 45 deg skirt of the same horizontal thickness up to the wall"),
    ("corner_r", 6.0, "outer corner radius"),
    ("cavity", 9.4, "panel back to the back plate = top of the board standoffs"
                    " (measured 13 from the panel front minus panel_t)"),
    ("ledge", 3.0, "back cover rim pressing on the panel border"),
    ("cable_side", 4, "cable exit: 0 = bottom wall, 1 = left, 2 = right (seen from the back),"
                      " 3 = hole in the back + snake groove, 4 = hole in the back only (the cable"
                      " goes down in the gap between the case and the wall)"),
    ("snake_x", -62.0, "rear cable hole centre X (seen from the back): past the end of the"
                       " USB-C plug, which points -X from the board edge at ~-25"),
    ("snake_y", 35.0, "rear cable hole centre Y (USB-C at ~33.5, clear of the keyhole)"),
    ("snake_hole_w", 13.0, "rear cable hole size so the USB-C plug passes"),
    ("snake_hole_h", 8.0, "snake: hole height"),
    ("snake_w", 5.0, "snake: groove width (cable dia ~3.5-4.5 mm, press in)"),
    ("snake_d", 5.0, "snake: groove depth (45 deg roof; a 4 mm cable still fits)"),
    ("snake_amp", 8.0, "snake: zigzag amplitude (X)"),
    ("snake_n", 3, "snake: number of zigzag bends"),
    ("cable_pos", -5.5, "cable slot centre along that wall (X for bottom, Y for sides);"
                        " -5.5 = in line with the driver board's USB-C (photo, relative to standoffs)"),
    ("cable_w", 9.0, "cable slot width (cable is laid in from the back, plug stays inside)"),
    ("cable_h", 15.0, "cable slot depth from the back face (cable rises over the panel clamp)"),
    ("cable_rear", 0, "1 = also a cable hole in the back plate (desk use)"),
    ("cable_y", -20.0, "rear cable hole centre Y from case centre"),
    ("key_span", 140.0, "distance between the two wall keyholes"),
    ("key_from_top", 35.0, "keyhole (narrow end) distance from the top edge"),
    ("key_head_d", 9.0, "keyhole: screw head entry diameter"),
    ("key_slot_w", 4.6, "keyhole: slot width (screw shank)"),
    ("key_slot_l", 10.0, "keyhole: slot length upwards from the entry"),
    ("feet_angle", 0.0, "desk tilt (deg); 0 = no feet (wall mount)"),
    ("osd_on", 1, "1 = slot in the back over the OSD buttons"),
    ("osd_x", 52.5, "OSD slot centre X (seen from the back, + right); buttons at ~42..44, push outwards"),
    ("osd_y_top", 41.5, "OSD slot top Y (buttons -12.5 .. +33.5; >= 2 mm from standoff 4 boss)"),
    ("osd_y_bot", -18.5, "OSD slot bottom Y (>= 2 mm from standoff 1 boss)"),
    ("osd_w", 18.0, "OSD slot width: a 12 mm finger + 6 mm, presses the buttons sideways"),
    ("feet_span", 110.0, "distance between the two desk feet"),
    ("screw_d", 3.4, "screw clearance hole in the back"),
    ("screw_head_d", 6.2, "screw head counterbore diameter"),
    ("screw_pilot", 2.6, "pilot hole in the bezel boss (2.6 self-tap M3, 4.0 insert)"),
    ("vent_n", 0, "number of vent slots in the back (0: the heatsink has its own window)"),
    ("vent_x", 6.0, "vent slots centre X (over the driver chip heatsink at ~(6, -2.4))"),
    ("vent_y", -2.4, "vent slots centre Y"),
    ("stand_on", 1, "1 = holes + bosses at the 4 driver-board standoffs"),
    # standoffs measured: spacing 62 x 70 mm; standoff 1 (bottom right seen from
    # the back, FPC edge down) at 124 mm from the left and 26.5 mm from the bottom
    # panel edge -> centre (124 - 82.35 - 31, 26.5 - 50 + 35)
    ("stand_cx", 10.65, "standoff rectangle centre X (seen from the back, + right)"),
    ("stand_cy", 11.5, "standoff rectangle centre Y (+ up)"),
    ("stand_dx", 63.0, "standoff spacing, horizontal (measured 62; +1 after the test print)"),
    ("stand_dy", 70.0, "standoff spacing, vertical (measured)"),
    ("board_margin", 6.0, "keep-out around the driver board (standoffs +/- this + 4.5 mm board overhang)"),
    ("board_top", 9.4, "height of the standoff tops above the panel back (13 from the panel front)"),
    ("stand_hole", 3.4, "screw hole over the two lower standoffs (M3 x 6, or M3 x 8 + washer)"),
    # parts sticking out above the standoff tops, positions from the photo
    # (same frame: seen from the back, FPC edge down)
    ("rad_x", 7.7, "heatsink centre X (14 x 14 mm, 4-5 mm above the standoffs)"),
    ("rad_y", -0.8, "heatsink window centre Y"),
    ("rad_win", 18.0, "heatsink window width (X)"),
    ("rad_win_h", 20.0, "heatsink window height (Y): 2 mm more downwards after the test print"),
    ("pico_x0", -17.0, "cap clear area over the Pico: X from (microUSB end)"),
    ("pico_x1", 40.5, "... X to (next to standoff 4)"),
    ("pico_y0", 24.0, "... Y from"),
    ("pico_y1", 52.0, "... Y to (the Pico sits at the panel edge)"),
    ("pico_top", 22.0, "top of the Pico above the panel front (measured)"),
    ("cap_clear", 1.5, "air above the Pico under the cap roof"),
    ("cap_lip", 1.4, "cap lip width (goes into the opening, wall is wall + lip thick)"),
    ("cap_fit", 0.2, "gap between the cap lip and the opening"),
    ("snap_n", 2, "snap fingers per long side of the cap (0 = glue it)"),
    ("snap_w", 8.0, "snap finger width"),
    ("snap_pitch", 28.0, "distance between the fingers on one side"),
    ("snap_hook", 1.2, "hook depth past the finger (1.0 past the opening edge; 0.8 did not hold)"),
    ("snap_play", 0.4, "hook top below the plate (print tolerance; 0.1 did not snap in)"),
    ("feet_on", 1, "1 = two spacer feet for the wall, screwed from inside (M3 x 8)"),
    ("foot_w", 14.0, "foot size"),
    ("foot_y", -42.0, "foot centre Y (X = +/- key_span / 2)"),
    ("boss_d", 9.0, "corner screw boss outer diameter in the back cover"),
    ("corner_floor", 3.9, "plastic under the corner head cones: M3 x 8 goes ~4.4 mm into the 4.8 mm pilot"),
    ("screw_inset", 6.0, "corner screws from both outer edges (= corner_r keeps them concentric)"),
    ("press_t", 1.6, "thickness of the frame pressing the panel border"),
]


def get_params(doc):
    sheet = doc.getObject("Params")
    if sheet is None:
        sheet = doc.addObject("Spreadsheet::Sheet", "Params")
        sheet.set("A1", "parameter")
        sheet.set("B1", "value")
        sheet.set("C1", "note")
        for i, (name, val, note) in enumerate(DEFAULTS, start=2):
            sheet.set("A%d" % i, name)
            sheet.set("B%d" % i, str(val))
            sheet.setAlias("B%d" % i, name)
            sheet.set("C%d" % i, note)
        doc.recompute()
    p = {}
    for name, val, _ in DEFAULTS:
        try:
            p[name] = float(sheet.get(name))
        except Exception:
            p[name] = float(val)
    return p


def rounded_box(w, h, d, r, z0=0.0, cx=0.0):
    """Box centred on (cx, 0), from z0 to z0 + d, vertical edges rounded with r."""
    if cx:
        return rounded_box(w, h, d, r, z0).translate(V(cx, 0, 0))
    r = max(0.01, min(r, w / 2 - 0.01, h / 2 - 0.01))
    box = Part.makeBox(w - 2 * r, h, d, V(-w / 2 + r, -h / 2, z0))
    box = box.fuse(Part.makeBox(w, h - 2 * r, d, V(-w / 2, -h / 2 + r, z0)))
    for sx in (-1, 1):
        for sy in (-1, 1):
            box = box.fuse(Part.makeCylinder(r, d, V(sx * (w / 2 - r), sy * (h / 2 - r), z0)))
    return box.removeSplitter()


def counterbore(x, y, z_floor, z_top, head_d, hole_d):
    """Screw head pocket from z_floor up to z_top, ending in a 45 deg cone down to
    the screw hole instead of a flat step: prints without supports (the pocket
    opens on the print bed, so its end is a ceiling)."""
    h = (head_d - hole_d) / 2
    pocket = Part.makeCylinder(head_d / 2, z_top - z_floor, V(x, y, z_floor))
    return pocket.fuse(Part.makeCone(hole_d / 2, head_d / 2, h, V(x, y, z_floor - h)))


def groove_path(points, w, z_face, d):
    """Groove of width w and depth d into the face at z_face (going -Z) along a
    polyline; its end is a 45 deg roof, so it prints as a ceiling without supports."""
    hw = w / 2
    straight = d - hw  # depth of the vertical walls, then the roof
    solid = None
    for (x1, y1), (x2, y2) in zip(points, points[1:]):
        length = math.hypot(x2 - x1, y2 - y1)
        prof = Part.makePolygon([V(0, -hw, z_face + 1), V(0, hw, z_face + 1), V(0, hw, z_face - straight),
                                 V(0, 0, z_face - d), V(0, -hw, z_face - straight), V(0, -hw, z_face + 1)])
        seg = Part.Face(prof).extrude(V(length, 0, 0))
        seg.rotate(V(0, 0, 0), V(0, 0, 1), math.degrees(math.atan2(y2 - y1, x2 - x1)))
        seg.translate(V(x1, y1, 0))
        solid = seg if solid is None else solid.fuse(seg)
    for (x, y) in points:  # round joints: cylinder + 45 deg cone roof
        solid = solid.fuse(Part.makeCylinder(hw, straight + 1, V(x, y, z_face - straight)))
        solid = solid.fuse(Part.makeCone(hw, 0, hw, V(x, y, z_face - straight), V(0, 0, -1)))
    return solid.removeSplitter()


def sweep_path(points, w, z0, d):
    """Solid of width w swept along a polyline (rounded joints), from z0 to z0 + d."""
    solid = None
    for (x1, y1), (x2, y2) in zip(points, points[1:]):
        length = math.hypot(x2 - x1, y2 - y1)
        seg = Part.makeBox(length, w, d, V(0, -w / 2, 0))
        seg.rotate(V(0, 0, 0), V(0, 0, 1), math.degrees(math.atan2(y2 - y1, x2 - x1)))
        seg.translate(V(x1, y1, z0))
        solid = seg if solid is None else solid.fuse(seg)
    for (x, y) in points:
        solid = solid.fuse(Part.makeCylinder(w / 2, d, V(x, y, z0)))
    return solid.removeSplitter()


def snake_exit(back, p, oh, zb, wl):
    """Cable hole in the back plate + zigzag groove in the back face down to the
    bottom edge, so the cable lies flush against the wall and is strain-relieved."""
    hx, hy = p["snake_x"], p["snake_y"]
    w, d, amp, n = p["snake_w"], p["snake_d"], p["snake_amp"], int(p["snake_n"])
    y_end = -oh / 2 - 1  # past the bottom edge
    y_start = hy - p["snake_hole_h"] / 2
    pts = [(hx, hy)]
    step = (y_start - (y_end + 8)) / (n + 1)
    for k in range(1, n + 1):
        pts.append((hx + (amp if k % 2 else 0), y_start - k * step))
    pts.append((pts[-1][0], y_end))
    floor = 1.6  # plastic left under the groove
    # rib inside the cover so the groove can be deeper than the back plate
    rib = sweep_path(pts, w + 2 * floor, zb - d - floor, d + floor - wl + 0.01)
    back = back.fuse(rib).removeSplitter()
    back = back.cut(groove_path(pts, w, zb, d))
    hole = rounded_box(p["snake_hole_w"], p["snake_hole_h"], d + floor + 2,
                       p["snake_hole_h"] / 2 - 0.01, zb - d - floor - 1)
    hole.translate(V(hx, hy, 0))
    return back.cut(hole)


def build(p):
    pw, ph = p["panel_w"] + 2 * p["fit"], p["panel_h"] + 2 * p["fit"]
    ow, oh = pw + 2 * p["border"], ph + 2 * p["border"]
    # The screen's left/right borders differ (seen from the front). With
    # frame_sym the case gets wider on the narrow-border side (left from the
    # front = +X) so the visible frame around the window is the same on both sides.
    ox = 0.0
    if p["frame_sym"]:
        extra = p["border_right"] - p["border_left"]
        ow += abs(extra)
        ox = extra / 2
    r = p["corner_r"]
    seam = p["front_t"] + p["panel_t"]  # bezel back face = panel back plane
    # corner screws sit in the centre of the corner rounding, so bosses and
    # counterbores stay concentric with the outer arc
    boss_x = ow / 2 - p["screw_inset"]
    boss_y = oh / 2 - p["screw_inset"]
    bosses = [(ox + sx * boss_x, sy * boss_y) for sx in (-1, 1) for sy in (-1, 1)]

    # --- bezel -----------------------------------------------------------
    wl = p["wall"]
    # the bezel sits inside the back's walls (rebate), lid_fit all around
    inset = wl + p["lid_fit"]
    bezel_box = lambda: rounded_box(ow - 2 * inset, oh - 2 * inset, seam, max(1.0, r - inset), 0.0, ox)
    bezel = bezel_box()
    # panel pocket, open to the back
    bezel = bezel.cut(Part.makeBox(pw, ph, p["panel_t"] + 1, V(-pw / 2, -ph / 2, p["front_t"])))
    # visible window (from the measured borders) with a 45 deg chamfer
    m = p["window_margin"]
    bl, br = p["border_left"] - m, p["border_right"] - m
    bt, bb = p["border_top"] - m, p["border_bottom"] - m
    # the screen's left border (seen from the front) is on the +X side
    x_l, x_r = -p["panel_w"] / 2 + br, p["panel_w"] / 2 - bl
    y_b, y_t = -p["panel_h"] / 2 + bb, p["panel_h"] / 2 - bt
    aw, ah = x_r - x_l, y_t - y_b
    cx, cy = (x_l + x_r) / 2, (y_b + y_t) / 2
    t = p["front_t"]
    win = Part.makeLoft([
        Part.makePolygon([V(cx - aw / 2 - t, cy - ah / 2 - t, -0.01), V(cx + aw / 2 + t, cy - ah / 2 - t, -0.01),
                          V(cx + aw / 2 + t, cy + ah / 2 + t, -0.01), V(cx - aw / 2 - t, cy + ah / 2 + t, -0.01),
                          V(cx - aw / 2 - t, cy - ah / 2 - t, -0.01)]),
        Part.makePolygon([V(cx - aw / 2, cy - ah / 2, t + 0.01), V(cx + aw / 2, cy - ah / 2, t + 0.01),
                          V(cx + aw / 2, cy + ah / 2, t + 0.01), V(cx - aw / 2, cy + ah / 2, t + 0.01),
                          V(cx - aw / 2, cy - ah / 2, t + 0.01)]),
    ], True)
    bezel = bezel.cut(win)
    # relief for the panel's FPC, which wraps around the bottom edge
    bezel = bezel.cut(Part.makeBox(p["fpc_w"], p["fpc_out"] + 1.0, p["panel_t"] + 1,
                                   V(p["fpc_x"] - p["fpc_w"] / 2, -ph / 2 - p["fpc_out"], p["front_t"])))
    # pilot holes for the screws (in the border, outside the panel)
    for (x, y) in bosses:
        bezel = bezel.cut(Part.makeCylinder(p["screw_pilot"] / 2, seam - 0.8, V(x, y, 0.8)))

    # --- back cover --------------------------------------------------------
    depth = p["cavity"] + p["wall"]
    z0 = seam
    zb = z0 + depth  # outer back face
    # thin shell open towards the front; the walls run up to the front face
    # (z = 0) and enclose the bezel
    back = rounded_box(ow, oh, zb, r, 0.0, ox)
    back = back.cut(rounded_box(ow - 2 * wl, oh - 2 * wl, zb - wl + 0.01, max(1.0, r - wl), -0.01, ox))
    # frame pressing the panel border against the bezel. Its inner face is a
    # 45 deg slope down to the wall, so the back prints without supports.
    iw, ih = pw - 2 * p["ledge"], ph - 2 * p["ledge"]
    cw_in, ch_in = ow - 2 * wl, oh - 2 * wl
    # slope height = widest overhang (the wall is farther on the widened side)
    d = max(cw_in / 2 + abs(ox) - iw / 2, (ch_in - ih) / 2) + 0.5
    rect = lambda w, h, z: Part.makePolygon([V(-w / 2, -h / 2, z), V(w / 2, -h / 2, z),
                                             V(w / 2, h / 2, z), V(-w / 2, h / 2, z), V(-w / 2, -h / 2, z)])
    slope = Part.makeLoft([rect(iw, ih, z0 + p["press_t"]), rect(iw + 2 * d, ih + 2 * d, z0 + p["press_t"] + d)], True)
    inner_hole = Part.makeBox(iw, ih, p["press_t"] + 0.02, V(-iw / 2, -ih / 2, z0 - 0.01)).fuse(slope)
    press = rounded_box(cw_in + 0.02, ch_in + 0.02, p["press_t"] + d, max(1.0, r - wl), z0, ox).cut(inner_hole)
    # hollow under the skirt: only a 45 deg plate of press_skirt (horizontal)
    # stays; the hollow opens to the front, so its roof faces up when printed
    k = p["press_skirt"]
    keep = Part.makeBox(iw + 2 * k, ih + 2 * k, p["press_t"] + 0.02, V(-iw / 2 - k, -ih / 2 - k, z0 - 0.01)).fuse(
        Part.makeLoft([rect(iw + 2 * k, ih + 2 * k, z0 + p["press_t"]),
                       rect(iw + 2 * k + 2 * d, ih + 2 * k + 2 * d, z0 + p["press_t"] + d)], True))
    press = press.cut(rounded_box(cw_in - 0.02, ch_in - 0.02, p["press_t"] + d, max(1.0, r - wl), z0 - 0.01, ox)
                      .cut(keep))
    press = press.common(rounded_box(cw_in + 0.1, ch_in + 0.1, zb - wl - z0 + 0.5, max(1.0, r - wl), z0 - 0.02, ox))
    back = back.fuse(press)
    # no clamping on the FPC where it lies on the panel back along the bottom edge
    back = back.cut(Part.makeBox(p["fpc_w"], p["ledge"] + p["fpc_out"] + 4, p["fpc_relief"] + 0.1,
                                 V(p["fpc_x"] - p["fpc_w"] / 2, -ph / 2 - p["fpc_out"], z0 - 0.1)))
    # screw bosses through the full depth, counterbored from the back
    for (x, y) in bosses:
        back = back.fuse(Part.makeCylinder(p["boss_d"] / 2, depth, V(x, y, z0)))
    back = back.removeSplitter()
    for (x, y) in bosses:
        back = back.cut(Part.makeCylinder(p["screw_d"] / 2, depth + 1, V(x, y, z0 - 0.5)))
        # deep counterbore: only corner_floor of plastic under the head -> short screws
        back = back.cut(counterbore(x, y, z0 + p["corner_floor"], zb + 1,
                                    p["screw_head_d"], p["screw_d"]))
    # cable slot in a wall, open at the back face (lay the cable in from the back)
    cw, ch, cp = p["cable_w"], p["cable_h"], p["cable_pos"]
    side = int(p["cable_side"])
    if side == 3:
        back = snake_exit(back, p, oh, zb, wl)
    elif side == 4:
        hole = rounded_box(p["snake_hole_w"], p["snake_hole_h"], wl + 2, p["snake_hole_h"] / 2 - 0.01, zb - wl - 1)
        back = back.cut(hole.translate(V(p["snake_x"], p["snake_y"], 0)))
    elif side == 0:
        back = back.cut(Part.makeBox(cw, wl + 2, ch + 0.5, V(cp - cw / 2, -oh / 2 - 1, zb - ch)))
    else:
        x0 = ox - ow / 2 - 1 if side == 1 else ox + ow / 2 - wl - 1
        back = back.cut(Part.makeBox(wl + 2, cw, ch + 0.5, V(x0, cp - cw / 2, zb - ch)))
    if p["cable_rear"]:
        slot = rounded_box(cw, ch, wl + 2, ch / 2 - 0.01, zb - wl - 1)
        slot.translate(V(0, p["cable_y"], 0))
        back = back.cut(slot)
    # vent slots in the upper middle of the back plate
    n = int(p["vent_n"])
    for k in range(n):
        vent = rounded_box(3.0, 28.0, wl + 2, 1.49, zb - wl - 1)
        vent.translate(V(p["vent_x"] + (k - (n - 1) / 2) * 9.0, p["vent_y"], 0))
        back = back.cut(vent)
    # keep-out for the driver board: nothing (e.g. the panel clamp near the top
    # edge) may reach into the board's footprint below the standoff tops
    if p["stand_on"]:
        bx0 = p["stand_cx"] - p["stand_dx"] / 2 - 4.5 - p["board_margin"]
        bx1 = p["stand_cx"] + p["stand_dx"] / 2 + 4.5 + p["board_margin"] + 3.0  # OSD buttons stick out
        by0 = p["stand_cy"] - p["stand_dy"] / 2 - 4.5 - p["board_margin"]
        by1 = p["stand_cy"] + p["stand_dy"] / 2 + 4.5 + p["board_margin"]
        keep = Part.makeBox(bx1 - bx0, by1 - by0, min(p["board_top"], p["cavity"]) + 0.1, V(bx0, by0, z0 - 0.1))
        # never cut the outer walls
        keep = keep.common(rounded_box(ow - 2 * wl, oh - 2 * wl, p["board_top"] + 0.2, max(1.0, r - wl), z0 - 0.1, ox))
        back = back.cut(keep)
    # the back plate lies on the board standoffs; M3 through the plate into the
    # two lower ones (the upper two are next to the Pico, under the cap)
    if p["stand_on"]:
        for sx in (-1, 1):
            x = p["stand_cx"] + sx * p["stand_dx"] / 2
            y = p["stand_cy"] - p["stand_dy"] / 2
            back = back.cut(Part.makeCylinder(p["stand_hole"] / 2, wl + 2, V(x, y, zb - wl - 1)))
    # window for the heatsink (sticks out 4-5 mm above the standoffs)
    rw = p["rad_win"]
    back = back.cut(rounded_box(rw, p["rad_win_h"], wl + 2, 2.0, zb - wl - 1).translate(V(p["rad_x"], p["rad_y"], 0)))
    # screw holes for the feet (screwed from inside, head on the plate)
    if p["feet_on"]:
        for sx in (-1, 1):
            back = back.cut(Part.makeCylinder(p["screw_d"] / 2, wl + 2,
                                              V(sx * p["key_span"] / 2, p["foot_y"], zb - wl - 1)))
    # opening for the cap over the Pico and the USB-C plug
    lip = p["cap_lip"]
    back = back.cut(cap_area(p, lip, zb - wl - 1, wl + 2))
    # access slot over the side-push OSD buttons of the driver board
    if p["osd_on"]:
        ow_ = p["osd_w"]
        oh_ = p["osd_y_top"] - p["osd_y_bot"]
        osd = rounded_box(ow_, oh_, wl + 2, ow_ / 2 - 0.01, zb - wl - 1)
        osd.translate(V(p["osd_x"], (p["osd_y_top"] + p["osd_y_bot"]) / 2, 0))
        back = back.cut(osd)
    # wall keyholes: enter at the round hole, slide down onto the slot end
    for sx in (-1, 1):
        x = sx * p["key_span"] / 2
        y_top = oh / 2 - p["key_from_top"]  # screw ends up here
        y_entry = y_top - p["key_slot_l"]
        back = back.cut(Part.makeCylinder(p["key_head_d"] / 2, wl + 2, V(x, y_entry, zb - wl - 1)))
        sw = p["key_slot_w"]
        slot = rounded_box(sw, p["key_slot_l"] + sw, wl + 2, sw / 2 - 0.01, zb - wl - 1)
        slot.translate(V(x, (y_top + y_entry) / 2, 0))
        back = back.cut(slot)
        # pocket inside so the screw head can slide (head entry diameter, 3 mm deep)
        pocket = rounded_box(p["key_head_d"], p["key_slot_l"] + p["key_head_d"], 3.0,
                             p["key_head_d"] / 2 - 0.01, zb - wl - 3.0)
        pocket.translate(V(x, (y_top + y_entry) / 2, 0))
        ring = rounded_box(p["key_head_d"] + 4, p["key_slot_l"] + p["key_head_d"] + 4, 3.0,
                           p["key_head_d"] / 2 + 1.99, zb - wl - 3.0)
        ring.translate(V(x, (y_top + y_entry) / 2, 0))
        back = back.fuse(ring.cut(pocket))
        back = back.cut(pocket)

    # desk feet: two wedges so the case leans back by feet_angle
    ang = p["feet_angle"]
    if ang > 0:
        fh = oh * 0.55  # foot reaches from the bottom edge up to here
        run = fh * math.tan(math.radians(ang))  # how far the foot sticks out
        for sx in (-1, 1):
            x = sx * p["feet_span"] / 2
            prof = Part.makePolygon([V(x - 4, -oh / 2, zb), V(x - 4, -oh / 2 + fh, zb),
                                     V(x - 4, -oh / 2, zb + run + 0.0), V(x - 4, -oh / 2, zb)])
            foot = Part.Face(prof).extrude(V(8, 0, 0))
            back = back.fuse(foot)
        back = back.removeSplitter()

    # nothing may stick out of the outer envelope (e.g. bosses near the corners)
    bezel = bezel.common(bezel_box()).removeSplitter()
    back = back.common(rounded_box(ow, oh, zb + 200, r, 0.0, ox)).removeSplitter() if p["feet_angle"] <= 0 else back
    return bezel, back, build_cap(p, zb, wl), build_feet(p, zb, wl)


def cap_area(p, grow, z0, d):
    """Clear area over the Pico grown by `grow`, from z0 to z0 + d."""
    x0, x1, y0, y1 = p["pico_x0"], p["pico_x1"], p["pico_y0"], p["pico_y1"]
    area = rounded_box(x1 - x0 + 2 * grow, y1 - y0 + 2 * grow, d, 1.0 + grow, z0)
    return area.translate(V((x0 + x1) / 2, (y0 + y1) / 2, 0))


def cap_top(p):
    """Outer roof plane of the cap = the plane that touches the wall."""
    return p["front_t"] + p["pico_top"] + p["cap_clear"] + p["wall"]


def build_cap(p, zb, wl):
    """Hump over the Pico: walls wall + lip thick standing on the back plate,
    the lip goes into the opening; roof at cap_top. Modelled roof up, exported
    roof down (prints without supports, the lip is the inner part of the wall)."""
    lip, fit = p["cap_lip"], p["cap_fit"]
    zt = cap_top(p)
    cap = cap_area(p, lip + wl, zb, zt - zb).fuse(cap_area(p, lip - fit, zb - wl, wl + 0.01))
    cap = cap.cut(cap_area(p, 0.0, zb - wl - 1, zt - wl - (zb - wl - 1))).removeSplitter()
    # vent slots in the roof over the Pico (RP2350 + Wi-Fi)
    for k in range(4):
        x = (p["pico_x0"] + p["pico_x1"]) / 2 + (k - 1.5) * 9.0
        cap = cap.cut(rounded_box(3.0, 14.0, wl + 2, 1.49, zt - wl - 1).translate(
            V(x, (p["pico_y0"] + p["pico_y1"]) / 2, 0)))
    return add_snaps(cap, p, zb, wl, zt)


def add_snaps(cap, p, zb, wl, zt):
    """Cantilever snap fingers in the long walls of the cap. Each finger is the
    inner lip-thick part of the wall, freed by two slits, hanging from the roof;
    below the plate it ends in an outward hook (45 deg lead-in) that clicks
    under the edge of the opening. The fingers flex ~0.6 mm while inserting."""
    n = int(p["snap_n"])
    if n <= 0:
        return cap
    lip, fit, w, hk = p["cap_lip"], p["cap_fit"], p["snap_w"], p["snap_hook"]
    t = lip - fit  # finger thickness = lip width
    z_plate = zb - wl  # inner face of the back plate
    z_catch = z_plate - p["snap_play"]  # hook top, below the plate
    z_slit = zt - wl - 1.5  # fingers hang from 1.5 mm below the roof
    cx = (p["pico_x0"] + p["pico_x1"]) / 2
    for side, y_in in ((-1, p["pico_y0"]), (1, p["pico_y1"])):
        for k in range(n):
            x = cx + (k - (n - 1) / 2) * p["snap_pitch"]
            # two slits through the wall + the outer part of the wall in front of the finger
            y0 = y_in - 0.1 if side > 0 else y_in - lip - wl - 0.5
            for sx in (-1, 1):
                cap = cap.cut(Part.makeBox(0.8, lip + wl + 0.6, z_slit - z_plate + wl + 1,
                                           V(x + sx * (w / 2 + 0.4) - 0.4, y0, z_plate - wl - 1)))
            y0 = y_in + t if side > 0 else y_in - lip - wl - 0.5
            cap = cap.cut(Part.makeBox(w, lip + wl - t + 0.5, z_slit - z_plate + 1, V(x - w / 2, y0, z_plate - 1)))
            # finger extension below the plate + hook
            y_out = y_in + side * t
            cap = cap.fuse(Part.makeBox(w, t, z_plate - (z_catch - hk) + 0.01, V(x - w / 2, min(y_in, y_out), z_catch - hk)))
            prof = Part.makePolygon([V(x - w / 2, y_out, z_catch), V(x - w / 2, y_out + side * hk, z_catch),
                                     V(x - w / 2, y_out, z_catch - hk), V(x - w / 2, y_out, z_catch)])
            cap = cap.fuse(Part.Face(prof).extrude(V(w, 0, 0)))
    return cap.removeSplitter()


def build_feet(p, zb, wl):
    """Two spacers as high as the cap, glued to the back near the bottom."""
    if not p["feet_on"]:
        return None
    zt = cap_top(p)
    feet = None
    for sx in (-1, 1):
        foot = rounded_box(p["foot_w"], p["foot_w"], zt - zb, 3.0, zb)
        foot.translate(V(sx * p["key_span"] / 2, p["foot_y"], 0))
        # pilot for the M3 x 8 through the 1.5 mm plate (6.5 mm in)
        x, y, pr = sx * p["key_span"] / 2, p["foot_y"], p["screw_pilot"] / 2
        foot = foot.cut(Part.makeCylinder(pr, 8.0, V(x, y, zb - 0.5)))
        foot = foot.cut(Part.makeCone(pr, 0, pr, V(x, y, zb + 7.5)))  # 45 deg end, no flat ceiling
        feet = foot if feet is None else feet.fuse(foot)
    return feet


def main():
    path = os.path.join(HERE, "case.FCStd")
    if os.path.exists(path):
        doc = App.openDocument(path)
    else:
        doc = App.newDocument("PicoDviCase")
    p = get_params(doc)
    bezel, back, cap, feet = build(p)
    parts = [("Bezel", bezel), ("Back", back), ("Cap", cap)] + ([("Feet", feet)] if feet else [])
    for name, shape in parts:
        obj = doc.getObject(name) or doc.addObject("Part::Feature", name)
        obj.Shape = shape
    if not feet and doc.getObject("Feet"):
        doc.removeObject("Feet")
    doc.recompute()
    doc.saveAs(path)

    import Mesh
    names = [n for n, _ in parts]
    for name in names:
        shape = doc.getObject(name).Shape
        # print orientation: bezel face down, feet as modelled; back cover
        # back down, cap roof down
        if name in ("Back", "Cap"):
            shape = shape.copy()
            shape.rotate(V(0, 0, 0), V(1, 0, 0), 180)
        mesh = Mesh.Mesh(shape.tessellate(0.05))
        mesh.write(os.path.join(HERE, name.lower() + ".stl"))
    Part.export([doc.getObject(n) for n in names], os.path.join(HERE, "case.step"))
    for name in names:
        s = doc.getObject(name).Shape
        bb = s.BoundBox
        print("%-6s %.1f x %.1f x %.1f mm, volume %.0f cm3, valid=%s"
              % (name, bb.XLength, bb.YLength, bb.ZLength, s.Volume / 1000, s.isValid()))


main()
